Ieee1609Dot2EndEntityMaInterfaceMbrBuilder
{iso(1) identified-organization(3) ieee(111)
standards-association-numbered-series-standards(2) wave-stds(1609)
dot2(2) scms(2) interfaces(1) ee-ma (7) mbr-builder(8)}

DEFINITIONS AUTOMATIC TAGS ::= BEGIN

EXPORTS ALL;

IMPORTS 
Certificate,
ToBeSignedData
FROM
IEEE1609dot2 {iso(1) identified-organization(3) ieee(111) 
standards-association-numbered-series-standards(2) wave-stds(1609)  
dot2(2) base (1) schema (1)}
;

CertificatePDU ::= Certificate

ToBeSignedDataPDU ::= ToBeSignedData

END
